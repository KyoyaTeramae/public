module openconfig-ospf {

  yang-version "1";

  // namespace
  namespace "http://openconfig.net/yang/ospf";

  prefix "oc-ospf";

  import openconfig-extensions { prefix "oc-ext"; }

  // Include submodules.
  include openconfig-ospf-global;
  include openconfig-ospf-area;
  include openconfig-ospf-area-interface;
  include openconfig-ospf-common;


  // meta
  organization "OpenConfig working group";

  contact
    "OpenConfig working group
    www.openconfig.net";

  description
    "This module provides common OSPF configuration and operational
    state parameters that are shared across multiple contexts";

  oc-ext:openconfig-version "0.2.0";

  revision "2026-09-06" {
    description
      "Add an nsr container to the OSPF global structure, matching
      the equivalent container on the ISIS global config.";
    reference "0.2.0";
  }
  revision "2025-08-10" {
    description
      "Removed duplicate import and updated prefixes in openconfig-ospf-area";
    reference "0.1.1";
  }
  revision "2025-02-13" {
    description
      "Initial revision";
    reference "0.0.1";
  }


  grouping ospfv3-top {
    description
      "Top-level OSPFv3 configuration and operational state";



    container ospfv3 {
      description
        "Top-level configuration and operational state for
        Open Shortest Path First (OSPF) v3";



      uses ospf-global-structural;



      container areas {
        description
          "Configuration and operational state relating to an
          OSPFv3 area.";



        list area {
          key "identifier";



          description
            "The OSPFv3 areas within which the local system exists";



          leaf identifier {
            type leafref {
              path "../config/identifier";
            }
            description
              "A reference to the identifier for the area.";
          }



          uses ospf-area-structure;
        }
      }
    }
  }

}
