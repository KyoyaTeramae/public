submodule openconfig-ospf-area-interface {

  belongs-to openconfig-ospf {
    prefix "oc-ospf";
  }

  import ietf-yang-types { prefix "yang"; }
  import ietf-inet-types { prefix "inet"; }
  import openconfig-extensions { prefix "oc-ext"; }
  import openconfig-types { prefix "oc-types"; }
  import openconfig-interfaces { prefix "oc-if"; }
  import openconfig-ospf-types { prefix "oc-ospf-types"; }
  import openconfig-bfd { prefix "oc-bfd"; }

  // include common submodule
  include openconfig-ospf-common;

  // meta
  organization "OpenConfig working group";

  contact
    "OpenConfig working group
    www.openconfig.net";

  description
    "This submodule provides common OSPF configuration and operational
    state parameters that are specific to the area context";

  oc-ext:openconfig-version "0.2.0";

  revision "2026-09-06" {
    description
      "Add send-default-route container to the OSPF global structure,
      allowing origination of a default external route, equivalent
      send-default-route of BGP global and neighbors config.";
    reference "0.2.0";
  }
  revision "2025-08-10" {
    description
      "Removed duplicate import and updated prefixes in openconfig-ospf-area";
    reference "0.1.1";
  }
  revision "2025-02-13" {
    description
      "Initial revision";
    reference "0.0.1";
  }

  grouping ospf-area-interface-config {
    description
      "Configuration parameters for an OSPF interface";

    leaf id {
      type string;
      description
        "An operator-specified string utilised to uniquely
        reference this interface";
    }

    leaf network-type {
      type identityref {
        base "oc-ospf-types:OSPF_NETWORK_TYPE";
      }
      description
        "The type of network that OSPF should use for the specified
        interface.";
    }

    leaf priority {
      type uint8;
      default 1;
      description
        "The local system's priority to become the designated
        router";
    }

    leaf multi-area-adjacency-primary {
      type boolean;
      default true;
      description
        "When the specified interface is included in more than one
        area's configuration, this leaf marks whether the area should
        be considered the primary (when the value is true). In the
        case that this value is false, the area is considered a
        secondary area.";
    }

    leaf authentication-type {
      type string;
      // rjs TODO: discuss with bogdanov@ what the approach for auth
      // links should be.
      description
        "The type of authentication that should be used on this
        interface";
    }

    leaf metric {
      type oc-ospf-types:ospf-metric;
      default 10;
      description
        "The metric for the interface";
    }

    leaf passive {
      type boolean;
      default false;
      description
        "When this leaf is set to true, the interface should be
        advertised within the OSPF area but OSPF adjacencies should
        not be established over the interface";
    }

    leaf hide-network {
      type boolean;
      description
        "When this leaf is set to true, the network connected to
        the interface should be hidden from OSPF advertisements
        per the procedure described in RFC6860.";
      reference
        "RFC6860 - Hiding Transit-Only Networks in OSFF";
    }

  }

  grouping ospf-area-interface-timers-config {
    description
      "Configuration parameters relating to per-interface OSPF
      timers";

    leaf dead-interval {
      type uint32;
      units seconds;
      default 40;
      description
        "The number of seconds that the local system should let
        elapse before declaring a silent router down";
      reference "RFC2328";
    }

    leaf hello-interval {
      type uint32;
      units seconds;
      default 10;
      description
        "The number of seconds the local system waits between the
        transmission of subsequent Hello packets";
    }

    leaf retransmission-interval {
      type uint32;
      units seconds;
      default 5;
      description
        "The number of seconds that the local system waits before
        retransmitting an unacknowledged LSA.";
    }

    leaf interface-transmission-delay {
      type uint32;
      units seconds;
      default 1;
      description
        "The estimated number of seconds it takes to transmit a Link State
         Update packet over this interface.";
    }
  }

  grouping ospf-area-interface-state {
    description
      "Operation state parameters of an OSPF interface";

    // TODO: Add the Interface state-machine state

    leaf dr-router-id {
      type yang:dotted-quad;
      description
        "The router-id of the designated router for this interface.";
    }

    leaf dr-ip-address {
      type inet:ip-address;
      description
        "The IP address of the designated router for this interface.";
    }

    leaf bdr-router-id {
      type yang:dotted-quad;
      description
        "The router-id of the backup designated router for this
        interface.";
    }

    leaf bdr-ip-address {
      type inet:ip-address;
      description
        "The IP address of the backup designated router for this
        interface.";
    }
  }

  grouping ospf-area-interface-neighbor-config {
    description
      "Configuration parameters relating to an individual neighbor
      system on an interface within an OSPF area";

    leaf neighbor-ip-address {
      type inet:ip-address;
      description
        "The IP address of the configured neighbor.";
    }

    leaf metric {
      type oc-ospf-types:ospf-metric;
      description
        "The metric that should be considered to the remote neighbor
        over this interface. This configuration is only applicable
        for multiple-access networks";
    }

    leaf poll-interval {
      type uint16;
      description
        "Neighbor poll interval (seconds) for sending OSPF Hello
        packets to discover the neighbor on NBMA networks. Refer
        Appendix C.5 in RFC 2328.";
    }

    leaf priority {
      type uint8;
      default 1;
      description
        "The local system's priority to become the designated router";
    }
  }

  grouping ospf-area-interface-neighbor-state {
    description
      "Operational state parameters relating an individual neighbor
      system on an interface within an OSPF area";

    leaf router-id {
      type yang:dotted-quad;
      description
        "The router ID of the remote system.";
    }

    leaf neighbor-ip-address {
      type inet:ip-address;
      description
        "The IP address of the remote system.";
    }

    leaf priority {
      type uint8;
      description
        "The remote system's priority to become the designated
        router";
    }

    leaf dead-time {
      type oc-types:timeticks64;
      description
        "The time at which this neighbor's adjacency will be
        considered dead. The value is expressed relative to
        the Unix Epoch (Jan 1, 1970 00:00:00 UTC).";
    }

    leaf dr-router-id {
      type yang:dotted-quad;
      description
        "The router ID of designated router for the adjacency. This device
        advertises the Network LSA for broadcast and NBMA networks.";
    }

    leaf dr-ip-address {
      type inet:ip-address;
      description
        "The IP address of designated router for the adjacency. This device
        advertises the Network LSA for broadcast and NBMA networks.";
    }

    leaf bdr-router-id {
      type yang:dotted-quad;
      description
        "The router ID of backup designated router for the adjacency.";
    }

    leaf bdr-ip-address {
      type inet:ip-address;
      description
        "The IP address of backup designated router for the adjacency.";
    }

    leaf optional-capabilities {
      // rjs TODO: should this be anything more than the hex-string
      // this is currently what is shown in IOS/JUNOS
      type yang:hex-string;
      description
        "The optional capabilities field received in the Hello
        message from the neighbor";
    }

    leaf last-established-time {
      type oc-types:timeticks64;
      // rjs TODO: check implementations - is FULL considered 'up'
      // since the adjacency is probably up since ExStart
      description
        "The time at which the adjacency was last established with
        the neighbor. That is to say the time at which the
        adjacency last transitioned into the FULL state. The
        value is expressed relative to the Unix Epoch (Jan 1 1970
        00:00:00 UTC).";
    }

    leaf adjacency-state {
      type identityref {
        base "oc-ospf-types:OSPF_NEIGHBOR_STATE";
      }
      description
        "The state of the adjacency with the neighbor.";
    }

    leaf state-changes {
      type uint32;
      description
        "The number of transitions out of the FULL state that this
        neighbor has been through";
    }

    leaf retransmission-queue-length {
      type uint32;
      description
        "The number of LSAs that are currently in the queue to be
        retransmitted to the neighbor";
    }
  }

  grouping ospf-area-interface-lsa-filter-config {
    description
      "Configuration options relating to filtering LSAs
      on an interface.";

    leaf all {
      type boolean;
      description
        "When this leaf is set to true, all LSAs should be
        filtered to the neighbours with whom adjacencies are
        formed on the interface.";
    }

    // NB: this container can be augmented to add additional
    // filtering options which exist in some implementations.
  }

  grouping ospf-area-interfaces-structure {
    description
      "Structural grouping for configuration and operational state
      parameters that relate to an interface";

    container interfaces {
      description
        "Enclosing container for a list of interfaces enabled within
        this area";

      list interface {
        key "id";

        description
          "List of interfaces which are enabled within this area";

        leaf id {
          type leafref {
            path "../config/id";
          }
          description
            "A pointer to the identifier for the interface.";
        }

        container config {
          description
            "Configuration parameters for the interface on which
            OSPF is enabled";

          uses ospf-area-interface-config;
        }

        container state {
          config false;
          description
            "Operational state parameters for the interface on which
            OSPF is enabled";
          uses ospf-area-interface-config;
          uses ospf-area-interface-state;
        }

        uses oc-if:interface-ref;

        container timers {
          description
            "Timers relating to OSPF on the interface";

          container config {
            description
              "Configuration parameters for OSPF timers on the
              interface";
            uses ospf-area-interface-timers-config;
          }

          container state {
            config false;
            description
              "Operational state parameters for OSPF timers on
              the interface";

            uses ospf-area-interface-timers-config;
          }
        }

        container lsa-filter {
          description
            "OSPF parameters relating to filtering of LSAs to
            neighbors the specified interface.";

          container config {
            description
              "Configuration parameters relating to filtering LSAs
              on the specified interface.";
            uses ospf-area-interface-lsa-filter-config;
          }

          container state {
            config false;
            description
              "Operational state parameters relating to filtering
              LSAs on the specified interface";
            uses ospf-area-interface-lsa-filter-config;
          }
        }

        container static-neighbors {
          description
            "Enclosing container for the list of statically
            configured neighbors";

          list static-neighbor {
            key "neighbor-ip-address";

            description
              "A neighbor which has been statically configured on
              this router";

            leaf neighbor-ip-address {
              type leafref {
                path "../config/neighbor-ip-address";
              }
              description
                "The IP address of the static neighbor.";
            }

            container config {
              description
                "Configuration parameters relating to the static
                neighbor";
              uses ospf-area-interface-neighbor-config;
            }

            container state {
              config false;
              description
                "Operational state parameters relating to the static
                neighbor";
              uses ospf-area-interface-neighbor-config;
            }
          }
        }

        container neighbors {
          config false;
          description
            "Enclosing container for the list of neighbors that
            an adjacency has been established with on the interface";

          list neighbor {
            key "router-id";

            description
              "A neighbor with which an OSPF adjacency has been
              established within this area";

            leaf router-id {
              type leafref {
                path "../state/router-id";
              }
              description
                "The router ID of the remote system.";
            }

            container state {
              config false;
              description
                "Operational state parameters relating to the adjacent
                system";
              uses ospf-area-interface-neighbor-state;
            }
          }
        }

        uses oc-bfd:bfd-enable;
      }
    }
  }
}
